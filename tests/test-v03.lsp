;;; Tests for Fancy Pencil 0.3 features: MTEXT box/width/justification, TEXT, TEXTEDIT.
;;; (The in-place editor itself is GUI-only; from AutoLISP these commands take text on the command line.)
(setq *pass* 0 *fail* 0)
(defun check (name got want)
  (if (equal got want 1e-6) (setq *pass* (1+ *pass*))
    (progn (setq *fail* (1+ *fail*))
           (princ (strcat "\nFAIL " name ": got " (vl-prin1-to-string got) " want " (vl-prin1-to-string want))))))
(defun g (e c) (cdr (assoc c (entget e))))
(setvar "OSMODE" 0) (setvar "CMDECHO" 0) (setvar "TEXTSIZE" 0.25)

;; MTEXT from two corners: insertion at top-left, width from the box
(command "mtext" '(1 8) '(7 5) "Hello" "World" "")
(setq m (entlast))
(check "mtext type" (g m 0) "MTEXT")
(check "mtext content" (g m 1) "Hello\\PWorld")
(check "mtext width" (g m 41) 6.0)
(check "mtext insertion" (g m 10) '(1.0 8.0 0.0))
(check "mtext attach" (g m 71) 1)
(check "mtext height" (g m 40) 0.25)

;; corners given bottom-right first still give a top-left box
(command "mtext" '(7 0) '(1 3) "x" "")
(check "mtext box normalised" (g (entlast) 10) '(1.0 3.0 0.0))

;; Height and Justify options
(command "mtext" '(0 0) "h" 0.5 "j" "MC" '(4 2) "Centered" "")
(setq m (entlast))
(check "mtext height option" (g m 40) 0.5)
(check "mtext MC attach" (g m 71) 5)
(check "mtext MC insertion" (g m 10) '(2.0 1.0 0.0))

;; Width option (no box)
(command "mtext" '(10 10) "w" 3 "Wide" "")
(check "mtext width option" (g (entlast) 41) 3.0)

;; empty text makes nothing
(setq before (entlast))
(command "mtext" '(0 0) '(2 2) "")
(check "empty mtext not created" (eq (entlast) before) T)

;; TEXT and TEXTEDIT
(command "text" '(0 -2) 0.3 0 "Single" "")
(setq t1 (entlast))
(check "dtext" (g t1 1) "Single")
(command "textedit" '(0.2 -1.9) "Changed" "")
(check "textedit" (g t1 1) "Changed")

;; ---------- text styles ----------
(command "-style" "Notes" "Arial" 0 1 0 "N" "N")
(check "style current" (getvar "TEXTSTYLE") "Notes")
(check "style tblsearch" (cdr (assoc 3 (tblsearch "STYLE" "Notes"))) "arial.ttf")
(command "-style" "Titles" "romans.shx" 0.5 0.8 15 "N" "N")
(setq s (tblsearch "STYLE" "Titles"))
(check "style fixed height" (cdr (assoc 40 s)) 0.5)
(check "style width" (cdr (assoc 41 s)) 0.8)
(check "style font file" (cdr (assoc 3 s)) "romans.shx")
;; fixed-height style: TEXT doesn't ask for a height
(command "text" '(0 -5) 0 "Titled" "")
(check "text uses style" (g (entlast) 7) "Titles")
(check "text fixed height" (g (entlast) 40) 0.5)
(setvar "TEXTSTYLE" "Notes")
(command "mtext" '(0 -8) '(5 -10) "In Notes, 25°" "")
(setq mn (entlast))
(check "mtext style" (g mn 7) "Notes")
;; DXF round trip (AutoCAD 2000 and R12) keeps styles and the degree sign
(command "saveas" "/tmp/fp-style-test.dxf")
(command "close")
(command "open" "/tmp/fp-style-test.dxf")
(check "2000: style kept" (cdr (assoc 3 (tblsearch "STYLE" "Titles"))) "romans.shx")
(check "2000: style width kept" (cdr (assoc 41 (tblsearch "STYLE" "Titles"))) 0.8)
(check "2000: notes font" (cdr (assoc 3 (tblsearch "STYLE" "Notes"))) "arial.ttf")
(setq m2 nil e (entnext))
(while e (if (= (g e 0) "MTEXT") (setq m2 e)) (setq e (entnext e)))
(check "2000: mtext text" (g m2 1) "In Notes, 25°")
(check "2000: mtext style" (g m2 7) "Notes")
(command "saveasr12" "/tmp/fp-style-r12.dxf")
(command "close")
(command "open" "/tmp/fp-style-r12.dxf")
(check "r12: style kept" (cdr (assoc 41 (tblsearch "STYLE" "Titles"))) 0.8)

;; ---------- several drawings open at once ----------
(command "closeall")
(defun count-all (/ s) (setq s (ssget "X")) (if s (sslength s) 0))
(command "line" '(0 0) '(1 1) "")
(command "line" '(0 1) '(1 2) "")
(setq name1 (getvar "DWGNAME"))
(setvar "OSMODE" 33)
(command "copyclip" (entlast) "")
(command "new")
(check "new tab is empty" (count-all) 0)
(check "new tab has its own name" (/= (getvar "DWGNAME") name1) T)
(check "osnap carried to new tab" (getvar "OSMODE") 33)
(command "circle" '(5 5) 1)
(command "pasteclip" '(3 3))
(check "paste from other tab" (count-all) 2)
(command "docprev")
(check "back in first tab" (getvar "DWGNAME") name1)
(check "first tab kept its objects" (count-all) 2)
(command "u")
(check "undo is per drawing" (count-all) 1)
(command "docnext")
(check "second tab untouched by undo" (count-all) 2)
(command "saveas" "/tmp/fp-tab2.dxf")
(command "open" "/tmp/fp-tab2.dxf")
(check "opening an open file switches to it" (getvar "DWGNAME") "fp-tab2.dxf")
(command "close")
(check "close returns to the other tab" (getvar "DWGNAME") name1)
(command "open" "/tmp/fp-tab2.dxf")
(check "reopened in a tab" (count-all) 2)
(command "docprev")
(check "both still open" (count-all) 1)

;; ---------- ALIGN ----------
(command "new")
(setvar "OSMODE" 0)
(command "line" '(0 0) '(2 0) "")
(setq al (entlast))
(command "align" al "" '(0 0) '(5 5) "")
(check "align one pair = move" (list (g al 10) (g al 11)) '((5.0 5.0 0.0) (7.0 5.0 0.0)))
(command "align" al "" '(5 5) '(10 10) '(7 5) '(10 12) "" "N")
(check "align rotates" (list (g al 10) (g al 11)) '((10.0 10.0 0.0) (10.0 12.0 0.0)))
(command "align" al "" '(10 10) '(0 0) '(10 12) '(3 4) "" "Y")
(check "align scales" (list (g al 10) (g al 11)) '((0.0 0.0 0.0) (3.0 4.0 0.0)))
;; ---------- arrowheads ----------
(setvar "DIMBLK" "_ArchTick")
(command "dimlinear" '(0 0) '(4 0) '(2 1))
(command "explode" (entlast) "")
(setq ss (ssget "X" '((0 . "SOLID"))))
(check "archtick drawn as filled strokes" (if ss (sslength ss) 0) 2)
(setvar "DIMBLK" "")
(command "-osnap" "END,MID,PER,TAN")
(check "-osnap" (getvar "OSMODE") (+ 1 2 128 256))

;; ---------- arrowheads survive DXF (R2000 and R12) ----------
(command "new")
(setvar "DIMBLK" "_ArchTick")
(command "-dimstyle" "save" "ArchT")
(setvar "DIMBLK" "_Dot")
(command "-dimstyle" "save" "DotS")
(command "-dimstyle" "restore" "ArchT")
(command "dimlinear" '(0 0) '(4 0) '(2 1))
(command "saveas" "/tmp/fp-arrows.dxf")
(command "saveasr12" "/tmp/fp-arrows12.dxf")
(command "close")
(command "open" "/tmp/fp-arrows.dxf")
(check "2000: current dim style restored" (getvar "DIMSTYLE") "ArchT")
(check "2000: archtick kept" (getvar "DIMBLK") "ARCHTICK")
(command "-dimstyle" "restore" "DotS")
(check "2000: dot kept" (getvar "DIMBLK") "DOT")
(command "close")
(command "open" "/tmp/fp-arrows12.dxf")
(command "-dimstyle" "restore" "ArchT")
(check "r12: archtick kept" (getvar "DIMBLK") "ARCHTICK")
(command "close")

;; ---------- repeating commands in any order (Recent Input list) ----------
(command "line" '(0 0) '(1 0) "")
(command "circle" '(5 5) 1)
(command "line" '(0 1) '(1 1) "")
(command "circle" '(6 6) 1)
(command "line" '(0 2) '(1 2) "")
(check "line after circle after line" (g (entlast) 10) '(0.0 2.0 0.0))

;; ---------- vertical dimensions, leaders and circular fills survive a save/open ----------
(command "new")
(setvar "DIMBLK" "")
(command "dimlinear" '(0 0) '(0 5) '(2 2.5))
(setq vd (entlast))
(check "vertical dim rotation" (< (abs (- (g vd 50) (/ pi 2))) 1e-9) T)
(entmake '((0 . "LEADER") (8 . "0") (71 . 1) (72 . 0) (10 0.0 0.0 0.0) (10 3.0 2.0 0.0) (10 5.0 2.0 0.0)))
(check "leader made" (g (entlast) 0) "LEADER")
(command "circle" '(10 10) 1)
(command "-hatch" "s" (entlast) "" "p" "solid" "")
(command "saveas" "/tmp/fp-objs.dxf")
(command "saveasr12" "/tmp/fp-objs12.dxf")
(command "close")
(command "open" "/tmp/fp-objs.dxf")
(setq ss (ssget "X" '((0 . "DIMENSION"))))
(check "2000: vertical dim still vertical" (< (abs (- (g (ssname ss 0) 50) (/ pi 2))) 1e-6) T)
(setq ld (ssget "X" '((0 . "LEADER"))))
(check "2000: leader kept" (if ld (sslength ld) 0) 1)
(check "2000: leader vertices" (length (vl-remove-if-not '(lambda (p) (= (car p) 10)) (entget (ssname ld 0)))) 3)
(command "close")
(command "open" "/tmp/fp-objs12.dxf")
(setq ss (ssget "X" '((0 . "DIMENSION"))))
(check "r12: vertical dim still vertical" (< (abs (- (g (ssname ss 0) 50) (/ pi 2))) 1e-6) T)
(command "close")

;; ---------- 0.3.13: circle radius from a picked point, -PLOT, SPELL ----------
(command "new")
(command "circle" '(0 0) '(3 4))
(check "circle radius from picked point" (g (entlast) 40) 5.0)
(command "line" '(0 0) '(10 5) "")
(command "text" '(1 1) 0.25 0 "BEDRROM recieve kitchen" "")
(vl-file-delete "/tmp/fp-plot.pdf")
(command "-plot" "" "Letter" "Landscape" "Extents" "Fit" "No" "/tmp/fp-plot.pdf")
(check "-PLOT writes a PDF" (if (findfile "/tmp/fp-plot.pdf") T nil) T)
(setq f (open "/tmp/fp-plot.pdf" "r"))
(check "PDF header" (substr (read-line f) 1 5) "%PDF-")
(close f)
(command "spell" "")
(command "close")

;; ---------- copy/paste between drawings carries layers, blocks and styles ----------
(command "new")
(command "-layer" "m" "CLIPWALLS" "c" "1" "" "")
(command "line" '(0 0) '(10 0) "")
(command "circle" '(2 2) 0.5)
(command "block" "CLIPCHAIR" '(2 2) (entlast) "")
(command "insert" "CLIPCHAIR" '(5 5) 1 1 0)
(command "-style" "ClipNotes" "romans.shx" 0 1 0 "n" "n")
(command "text" '(0 8) 0.25 0 "PASTE ME" "")
(setvar "CLAYER" "0")
(command "copyclip" "all" "")
(command "new")
(command "pasteclip" '(100 100))
(check "paste: objects" (sslength (ssget "X")) 4)
(check "paste: layer colour" (cdr (assoc 62 (tblsearch "LAYER" "CLIPWALLS"))) 1)
(check "paste: block" (if (tblsearch "BLOCK" "CLIPCHAIR") T nil) T)
(check "paste: text style" (if (tblsearch "STYLE" "ClipNotes") T nil) T)
(check "paste: position" (cdr (assoc 10 (entget (ssname (ssget "X" '((0 . "LINE"))) 0)))) '(100.0 100.0 0.0))
(command "pasteorig")
(check "pasteorig" (sslength (ssget "X")) 8)
(command "pasteblock" '(0 50))
(check "pasteblock" (sslength (ssget "X")) 9)
(command "close")
(command "close")

;; ---------- MATCHPROP: basic and special properties ----------
(command "new")
(command "-layer" "m" "MPRED" "c" "1" "" "")
(command "line" '(0 0) '(10 0) "")
(setq mps (entlast))
(command "-layer" "s" "0" "")
(command "circle" '(5 5) 1)
(setq mpc (entlast))
(command "matchprop" mps mpc "")
(check "matchprop layer" (g mpc 8) "MPRED")
(command "-style" "MPBig" "romans.shx" 0 0.8 0 "n" "n")
(command "text" '(0 10) 0.5 0 "SOURCE" "")
(setq mpt1 (entlast))
(command "-style" "Standard" "" 0 1 0 "n" "n")
(command "text" '(0 12) 0.2 0 "dest" "")
(setq mpt2 (entlast))
(command "matchprop" mpt1 mpt2 "")
(check "matchprop text style" (g mpt2 7) "MPBig")
(check "matchprop text height" (g mpt2 40) 0.5)
(command "-hatch" "p" "ANSI37" 2 45 "s" mpc "" "")
(setq mph1 (entlast))
(command "circle" '(20 5) 1)
(command "-hatch" "p" "SOLID" "s" (entlast) "" "")
(setq mph2 (entlast))
(command "matchprop" mph1 mph2 "")
(check "matchprop hatch pattern" (list (g mph2 2) (g mph2 41)) '("ANSI37" 2.0))
(command "pline" '(0 20) "w" 0.3 0.3 '(5 20) '(5 25) "")
(setq mpp1 (entlast))
(command "pline" '(10 20) '(15 20) '(15 25) "")
(setq mpp2 (entlast))
(command "matchprop" mpp1 mpp2 "")
(check "matchprop polyline width" (g mpp2 43) 0.3)
(command "dimlinear" '(0 30) '(10 30) '(5 32))
(setq mpd1 (entlast))
(command "-dimstyle" "s" "MPARCH")
(command "dimlinear" '(0 40) '(10 40) '(5 42))
(setq mpd2 (entlast))
(command "matchprop" mpd2 mpd1 "")
(check "matchprop dimension style" (g mpd1 3) "MPARCH")
(command "matchprop" mps "s" "Layer" "" mpp2 "")
(check "matchprop settings: layer off" (g mpp2 8) "0")
(command "matchprop" mps "s" "All" "" "")
(command "close")

;; ---------- no-plot layers, ALIGN scale ----------
(command "new")
(command "-layer" "m" "NPNOTES" "p" "n" "NPNOTES" "")
(check "no-plot layer flag" (cdr (assoc 290 (tblsearch "LAYER" "NPNOTES"))) 0)
(command "-layer" "s" "0" "")
(command "line" '(0 0) '(1 1) "")
(command "saveas" "/tmp/fp-np2.dxf")
(command "close")
(command "open" "/tmp/fp-np2.dxf")
(check "no-plot survives save" (cdr (assoc 290 (tblsearch "LAYER" "NPNOTES"))) 0)
(check "plot layer stays plot" (cdr (assoc 290 (tblsearch "LAYER" "0"))) 1)
(command "close")
(command "new")
(command "line" '(0 0) '(2 0) "")
(command "align" (entlast) "" '(0 0) '(10 10) '(2 0) '(10 16) "" "y")
(check "align with scaling" (g (entlast) 11) '(10.0 16.0 0.0))
(command "line" '(0 0) '(2 0) "")
(command "align" (entlast) "" '(0 0) '(10 10) '(2 0) '(10 16) "" "n")
(check "align without scaling" (g (entlast) 11) '(10.0 12.0 0.0))
(command "close")

;; ---------- scaling MTEXT keeps its box; AL alias ----------
(command "new")
(command "mtext" '(0 2) '(3 1) "Kitchen note" "")
(setq mt (entlast))
(command "scale" mt "" '(0 0) 10)
(check "mtext height scales" (g mt 40) (* 10 (getvar "TEXTSIZE")))
(check "mtext box width scales" (g mt 41) 30.0)
(command "line" '(0 0) '(2 0) "")
(command "al" (entlast) "" '(0 0) '(10 10) '(2 0) '(10 16) "" "y")
(check "AL runs ALIGN" (g (entlast) 11) '(10.0 16.0 0.0))
(command "close")

;; ---------- units, blocks ----------
(command "new")
(setvar "LUNITS" 4) (setvar "LUPREC" 4)
(check "architectural rtos" (rtos 150.5) "12'-6 1/2\"")
(command "units" 2 4 0 0)
(check "UNITS command line" (list (getvar "LUNITS") (getvar "LUPREC")) '(2 4))
(setvar "LUNITS" 4) (setvar "LTSCALE" 24.0)
(command "line" '(0 0) '(10 0) "")
(command "saveas" "/tmp/fp-units.dxf")
(command "close")
(command "open" "/tmp/fp-units.dxf")
(check "units saved in drawing" (getvar "LUNITS") 4)
(check "ltscale saved in drawing" (getvar "LTSCALE") 24.0)
(setvar "LUNITS" 2)
(command "close")
(command "new")
(command "rectang" '(1 1) '(5 3))
(command "circle" '(3 2) 0.5)
(command "-block" "BLKTEST" '(1 1) "all" "")
(check "-BLOCK converts to insert" (list (g (entlast) 0) (g (entlast) 2)) '("INSERT" "BLKTEST"))
(check "block definition" (if (tblsearch "BLOCK" "BLKTEST") T nil) T)
(command "-block" "bad*name")
(check "invalid block name refused" (tblsearch "BLOCK" "bad*name") nil)
(command "close")

;; ---------- block editor, rename ----------
(command "new")
(command "circle" '(5 5) 1)
(command "-block" "BECH" '(5 5) (entlast) "")
(command "insert" "BECH" '(20 20) 1 1 0)
(command "bedit" "BECH")
(check "block editor tab" (getvar "DWGNAME") "Block Editor: BECH")
(check "block contents at base point" (g (entlast) 10) '(0.0 0.0 0.0))
(command "line" '(0 0) '(3 0) "")
(command "bclose")
(check "back in the drawing" (/= (getvar "DWGNAME") "Block Editor: BECH") T)
(command "explode" (entlast) "")
(check "edited block has the new line" (sslength (ssget "X" '((0 . "LINE")))) 1)
(command "u")
(command "u")
(command "explode" (entlast) "")
(check "undo restores the block" (ssget "X" '((0 . "LINE"))) nil)
(command "u")
(command "rename" "block" "BECH" "BECHAIR")
(check "rename block" (list (g (entlast) 2) (if (tblsearch "BLOCK" "BECHAIR") T nil)) '("BECHAIR" T))
(command "close")

;; ---------- isometric drafting, views, thickness, layer controls ----------
(command "new")
(command "isodraft" "isoplaneTop")
(check "isodraft on" (getvar "SNAPSTYL") 1)
(command "ellipse" "i" '(0 0) 2)
(check "isocircle ratio" (< (abs (- (g (entlast) 40) (/ 1 (sqrt 3)))) 1e-6) T)
(check "isocircle top axis" (< (abs (- (car (g (entlast) 11)) (* 2 (sqrt 1.5)))) 1e-6) T)
(command "isoplane" "Left")
(check "isoplane left" (getvar "SNAPISOPAIR") 0)
(command "isodraft" "Orthographic")
(check "isodraft off" (getvar "SNAPSTYL") 0)
(setvar "THICKNESS" 2.5)
(command "line" '(0 0) '(5 0) "")
(check "thickness on new line" (g (entlast) 39) 2.5)
(setvar "THICKNESS" 0.0)
(command "-view" "SWiso")
(command "line" '(0 5) '(5 5) "")
(check "drawing in an iso view" (g (entlast) 11) '(5.0 5.0 0.0))
(command "plan")
(command "-layer" "m" "LC1" "")
(command "line" '(0 9) '(1 9) "")
(setq lc1 (entlast))
(command "-layer" "m" "LC2" "")
(command "line" '(0 10) '(1 10) "")
(command "laymch" (entlast) "" lc1)
(check "match layer" (g (entlast) 8) "LC1")
(command "-layer" "s" "LC2" "")
(command "laymcur" lc1)
(check "make object's layer current" (getvar "CLAYER") "LC1")
(command "line" '(0 11) '(1 11) "")
(setq cl1 (entlast))
(command "line" '(0 12) '(1 12) "")
(command "changelayer" cl1 (entlast) "" "LC2")
(check "change layer" (list (g cl1 8) (g (entlast) 8)) '("LC2" "LC2"))
(command "changelayer" cl1 "" "")
(check "change layer to current" (g cl1 8) "LC1")
(command "close")

;; ---------- point style ----------
(command "new")
(command "ddptype" 35 -5)
(check "point style mode" (getvar "PDMODE") 35)
(check "point style size" (getvar "PDSIZE") -5.0)
(command "point" '(3 3))
(vl-file-delete "/tmp/fp-pts.pdf")
(command "-plot" "" "Letter" "Landscape" "Extents" "Fit" "No" "/tmp/fp-pts.pdf")
(check "points plot" (if (findfile "/tmp/fp-pts.pdf") T nil) T)
(command "close")

;; ---------- renaming a layer (objects inside blocks follow) ----------
(command "new")
(command "-layer" "m" "OLDL" "")
(command "line" '(0 0) '(1 0) "")
(command "-block" "RLB" '(0 0) (entlast) "")
(command "line" '(5 5) '(6 5) "")
(command "-layer" "s" "0" "")
(command "rename" "layer" "OLDL" "NEWL")
(check "renamed layer exists" (if (tblsearch "LAYER" "NEWL") T nil) T)
(check "old name gone" (tblsearch "LAYER" "OLDL") nil)
(check "object on renamed layer" (g (entlast) 8) "NEWL")
(command "-insert" "RLB" '(10 10) 1 1 0)
(command "explode" (entlast) "")
(check "object inside the block follows" (g (entlast) 8) "NEWL")
(command "close")

;; ---------- plotting an isometric view ----------
(command "new")
(command "rectang" '(0 0) '(8 5))
(command "text" '(1 6) 0.6 0 "ISO" "")
(command "-view" "swiso")
(vl-file-delete "/tmp/fp-iso.pdf")
(command "-plot" "" "Letter" "Landscape" "Extents" "Fit" "No" "/tmp/fp-iso.pdf")
(check "isometric view plots" (if (findfile "/tmp/fp-iso.pdf") T nil) T)
(command "plan")
(command "close")

;; ---------- leaders ----------
(defun entbefore (e / x prev) (setq x (entnext)) (while (and x (not (eq x e))) (setq prev x x (entnext x))) prev)
(command "new")
(command "leader" '(0 0) '(2 2) "" "FIRST LINE" "SECOND" "")
(setq tx (entlast))
(check "leader note is mtext" (g tx 0) "MTEXT")
(check "leader note text" (g tx 1) "FIRST LINE\\PSECOND")
(setq ld (entbefore tx))
(check "leader object" (g ld 0) "LEADER")
(check "leader arrow on" (g ld 71) 1)
(check "leader straight" (g ld 72) 0)
(check "leader landing added" (length (vl-remove-if-not '(lambda (p) (= (car p) 10)) (entget ld))) 3)
(check "note right of landing" (> (car (g tx 10)) 2.0) T)
(command "leader" '(10 0) "S" '(8 1) '(6 1) "NOText")
(check "spline leader" (g (entlast) 72) 1)
(check "no text: no landing" (length (vl-remove-if-not '(lambda (p) (= (car p) 10)) (entget (entlast)))) 3)
(command "leader" '(20 0) "ST" "None" '(18 3) "" "")
(check "straight again, no arrow" (list (g (entlast) 72) (g (entlast) 71)) '(0 0))
(command "leader" "Arrow" '(30 0) '(28 3) "U" '(26 0) "" "LEFT" "")
(check "leftward note right-attached" (g (entlast) 71) 3)
(check "undo leader point" (length (vl-remove-if-not '(lambda (p) (= (car p) 10)) (entget (entbefore (entlast))))) 2)
(command "-layer" "m" "NOTES" "")
(command "leader" '(40 0) '(42 2) "" "ON NOTES" "")
(check "hooked leader keeps its layer" (g (entbefore (entlast)) 8) "NOTES")
(command "close")

(princ (strcat "\nv0.3 tests: " (itoa *pass*) " passed, " (itoa *fail*) " failed.\n"))
(princ)
