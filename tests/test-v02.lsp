;;; Tests for Fancy Pencil 0.2 features: linetypes, lineweights, hatching, polyline trim/extend,
;;; fillet/chamfer, PEDIT, dimensions & styles, Express Tools, acet-* functions, aliases, DXF 2000.
(setq *pass* 0 *fail* 0)
(defun check (name got want)
  (if (equal got want 1e-6) (setq *pass* (1+ *pass*))
    (progn (setq *fail* (1+ *fail*))
           (princ (strcat "\nFAIL " name ": got " (vl-prin1-to-string got) " want " (vl-prin1-to-string want))))))
(defun pt= (a b) (< (distance a b) 1e-6))
(defun g (e c) (cdr (assoc c (entget e))))
(defun n-of (ty / s) (setq s (ssget "X" (list (cons 0 ty)))) (if s (sslength s) 0))
(setvar "OSMODE" 0) (setvar "CMDECHO" 0)

;; ---------- linetypes & lineweights ----------
(command "-linetype" "load" "HIDDEN,CENTER" "" "")
(check "ltype loaded" (cdr (assoc 2 (tblsearch "LTYPE" "HIDDEN"))) "HIDDEN")
(setvar "CELTYPE" "HIDDEN")
(command "line" '(0 0) '(10 0) "")
(check "entity ltype" (g (entlast) 6) "HIDDEN")
(setvar "CELTYPE" "BYLAYER")
(setvar "CELWEIGHT" 50)
(command "line" '(0 1) '(10 1) "")
(check "entity lineweight" (g (entlast) 370) 50)
(setvar "CELWEIGHT" -1)
(command "-layer" "make" "CL" "ltype" "CENTER" "CL" "lweight" "0.35" "CL" "")
(check "layer ltype via -LAYER" (cdr (assoc 6 (tblsearch "LAYER" "CL"))) "CENTER")
(setvar "CLAYER" "0")
(command "chprop" (entlast) "" "LType" "CENTER" "ltScale" 2 "")
(check "chprop ltype" (g (entlast) 6) "CENTER")
(check "chprop ltscale" (g (entlast) 48) 2.0)

;; ---------- hatch ----------
(command "rectang" '(100 0) '(110 10))
(command "circle" '(105 5) 2)
(command "-hatch" "P" "ANSI31" 1 0 '(101 1) "")
(setq h (entlast))
(check "hatch created" (g h 0) "HATCH")
(defun loops-of (e) (length (vl-remove-if-not '(lambda (x) (= (car x) 92)) (entget e))))
(check "hatch has island" (loops-of h) 2)
(check "hatch pattern" (g h 2) "ANSI31")
(command "-hatch" "P" "SOLID" '(105 5) "")
(check "solid hatch inside circle" (g (entlast) 70) 1)
(check "solid hatch one loop" (loops-of (entlast)) 1)
;; boundary made of separate lines
(command "line" '(200 0) '(210 0) '(210 10) '(200 10) "C")
(command "-hatch" "P" "NET" 1 0 '(205 5) "")
(check "hatch from lines" (g (entlast) 0) "HATCH")
(command "move" (entlast) "" '(0 0) '(0 20))
(check "hatch moves" (< 19.9 (caddr (assoc 10 (member (assoc 93 (entget (entlast))) (entget (entlast)))))) T)
;; entmod round trip: change the pattern scale through AutoLISP
(setq hd (entget (entlast)))
(entmod (subst (cons 41 2.0) (assoc 41 hd) hd))
(check "hatch entmod" (cdr (assoc 41 (entget (entlast)))) 2.0)

;; ---------- polyline trim / extend ----------
(command "pline" '(0 50) '(10 50) '(10 60) "")
(setq pl (entlast))
(command "line" '(5 45) '(5 55) "")
(setq cut (entlast))
(command "trim" cut "" (list pl '(2 50)) "")
(check "trim polyline keeps rest" (pt= (cdr (assoc 10 (entget pl))) '(5.0 50.0)) T)
(check "trim polyline vertices" (g pl 90) 3)
(command "rectang" '(20 50) '(30 60))
(setq rp (entlast))
(command "line" '(25 45) '(25 65) "")
(setq cut2 (entlast))
(command "trim" cut2 "" (list rp '(20 55)) "")
(check "trim closed polyline opens it" (logand 1 (g rp 70)) 0)
(command "pline" '(40 50) '(45 50) "")
(setq ep (entlast))
(command "line" '(50 45) '(50 55) "")
(command "extend" (entlast) "" (list ep '(44 50)) "")
(check "extend polyline" (pt= (cdr (last (vl-remove-if-not '(lambda (x) (= (car x) 10)) (entget ep)))) '(50.0 50.0)) T)

;; ---------- fillet / chamfer ----------
(setvar "FILLETRAD" 1.0)
(command "line" '(0 80) '(10 80) "") (setq fa (entlast))
(command "arc" "C" '(15 80) '(15 85) "A" -90)
(setq fb (entlast))
(command "fillet" (list fa '(5 80)) (list fb '(18 84)))
(check "fillet line+arc makes arc" (g (entlast) 0) "ARC")
(check "fillet arc radius" (g (entlast) 40) 1.0)
(command "rectang" '(30 80) '(40 90))
(setq fr (entlast))
(command "fillet" "P" fr)
(check "fillet polyline vertices" (g fr 90) 8)
(check "fillet polyline bulge" (/= 0.0 (abs (cdr (assoc 42 (entget fr))))) T)
(setvar "CHAMFERA" 1.0) (setvar "CHAMFERB" 1.0)
(command "rectang" '(50 80) '(60 90))
(command "chamfer" "P" (entlast))
(check "chamfer polyline" (g (entlast) 90) 8)

;; ---------- PEDIT ----------
(command "line" '(0 100) '(5 100) "") (setq p1 (entlast))
(command "line" '(5 100) '(5 105) "") (setq p2 (entlast))
(command "pedit" p1 "Y" "Join" p2 "" "Close" "Width" 0.2 "")
(setq pe (entlast))
(check "pedit join" (g pe 90) 3)
(check "pedit close" (logand 1 (g pe 70)) 1)
(check "pedit width" (g pe 43) 0.2)

;; ---------- dimensions ----------
(command "circle" '(0 130) 3) (setq dc (entlast))
(command "dimradius" (list dc '(3 130)) '(6 133))
(check "dimradius" (g (entlast) 42) 3.0)
(command "dimdiameter" (list dc '(3 130)) '(1 131))
(check "dimdiameter" (g (entlast) 42) 6.0)
(command "line" '(10 130) '(20 130) "") (setq a1 (entlast))
(command "line" '(10 130) '(20 140) "") (setq a2 (entlast))
(command "dimangular" (list a1 '(15 130)) (list a2 '(15 135)) '(18 132))
(check "dimangular 45 deg" (g (entlast) 42) (/ pi 4))
(command "dimlinear" '(0 150) '(5 150) '(2 148))
(command "dimcontinue" '(12 150) "")
(check "dimcontinue measurement" (g (entlast) 42) 7.0)
(command "dimlinear" '(0 160) '(5 160) '(2 158))
(command "dimbaseline" '(9 160) "")
(check "dimbaseline measurement" (g (entlast) 42) 9.0)
(setvar "DIMTXT" 0.25)
(command "-dimstyle" "save" "BIG")
(setvar "DIMTXT" 0.1)
(command "-dimstyle" "restore" "BIG")
(check "dimstyle restore" (getvar "DIMTXT") 0.25)
(check "dimstyle current" (getvar "DIMSTYLE") "BIG")

;; ---------- Express Tools ----------
(command "line" '(0 200) '(10 200) "")
(command "line" '(0 200) '(10 200) "")
(command "line" '(5 200) '(15 200) "")
(command "overkill" "ALL" "")
(setq ok (ssget "X" '((0 . "LINE") (-4 . "*,=,*") (10 0.0 200.0 0.0))))
(check "overkill leaves one line" (sslength ok) 1)
(check "overkill merged overlap" (pt= (g (ssname ok 0) 11) '(15 200 0)) T)
(command "-layer" "make" "ISO" "")
(setvar "CLAYER" "0")
(command "text" '(0 210) 0.2 0 "alpha" "")
(setq t1 (entlast))
(command "text" '(0 209) 0.2 0 "beta" "")
(setq t2 (entlast))
(command "tcase" t1 t2 "" "UPPER")
(check "tcase" (g t1 1) "ALPHA")
(command "tcount" t1 t2 "" "Y" "1,1" "Prefix")
(check "tcount" (g t2 1) "2 BETA")
(command "txt2mtxt" t1 t2 "")
(check "txt2mtxt" (g (entlast) 0) "MTEXT")
(command "laycur" (entlast) "")
(command "-layer" "set" "ISO" "")
(command "line" '(0 220) '(1 220) "")
(setvar "CLAYER" "0")
(command "layiso" (entlast) "")
(check "layiso turns others off" (minusp (cdr (assoc 62 (tblsearch "LAYER" "CL")))) T)
(command "layuniso")
(check "layuniso restores" (minusp (cdr (assoc 62 (tblsearch "LAYER" "CL")))) nil)
(command "breakline" '(0 230) '(10 230) "")
(check "breakline" (g (entlast) 90) 6)
(command "circle" '(50 230) 3) (setq xc (entlast))
(command "line" '(40 230) '(60 230) "") (setq xl (entlast))
(command "extrim" xc '(50 230))
(check "extrim removes inside" (pt= (g xl 11) '(47 230 0)) T)
;; ---------- acet-* ----------
(check "acet-str-replace" (acet-str-replace "a" "o" "banana") "bonono")
(check "acet-str-find" (acet-str-find "na" "banana") 3)
(check "acet-geom-midpoint" (acet-geom-midpoint '(0 0 0) '(2 2 0)) '(1.0 1.0 0.0))
(check "acet-list-remove-duplicates" (acet-list-remove-duplicates '(1 2 1 3 2) nil) '(1 2 3))
(acet-error-init (list (list "OSMODE" 33) T))
(check "acet-error-init sets" (getvar "OSMODE") 33)
(acet-error-restore)
(check "acet-error-restore" (getvar "OSMODE") 0)
(check "acet-str-format" (acet-str-format "%1 of %2" 3 "7") "3 of 7")

;; ---------- aliases ----------
(defun c:hello () (setq *hello* T) (princ))
(command "aliasedit" "Add" "HH" "HELLO" "eXit")
(check "alias added" (fancypencil-alias "HH") "HELLO")

;; ---------- DXF 2000 round trip ----------
(setq before (sslength (ssget "X")))
(command "saveas" "/tmp/v02-test.dxf")
(command "new")
(command "open" "/tmp/v02-test.dxf")
(check "dxf2000 count" (sslength (ssget "X")) before)
(check "dxf2000 hatch kept" (> (n-of "HATCH") 2) T)
(check "dxf2000 ltype kept" (cdr (assoc 6 (tblsearch "LAYER" "CL"))) "CENTER")
(check "dxf2000 lineweight kept" (> (sslength (ssget "X" '((370 . 50)))) 0) T)
(check "dxf2000 dim kept" (> (n-of "DIMENSION") 5) T)
(check "dxf2000 dimstyle kept" (cdr (assoc 2 (tblsearch "DIMSTYLE" "BIG"))) "BIG")

(princ (strcat "\nv0.2 tests: " (itoa *pass*) " passed, " (itoa *fail*) " failed.\n"))
(princ)
