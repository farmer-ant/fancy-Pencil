;;; Drafting tests driven through (command ...), entget/entmod and selection sets.
(setq *pass* 0 *fail* 0)
(defun check (name got want)
  (if (equal got want 1e-6)
    (setq *pass* (1+ *pass*))
    (progn (setq *fail* (1+ *fail*))
           (princ (strcat "\nFAIL " name ": got " (vl-prin1-to-string got) " want " (vl-prin1-to-string want))))))
(defun pt= (a b) (< (distance a b) 1e-6))
(setvar "OSMODE" 0)
(setvar "CMDECHO" 0)

;; LINE in one call
(command "_.line" '(0 0) '(10 0) "")
(setq e1 (entlast))
(check "line type" (cdr (assoc 0 (entget e1))) "LINE")
(check "line end" (pt= (cdr (assoc 11 (entget e1))) '(10 0 0)) T)
;; LINE split across calls, like AutoCAD
(command "line" '(0 5) '(5 5))
(check "cmdactive" (getvar "CMDACTIVE") 1)
(command '(5 10) "")
(check "cmdactive done" (getvar "CMDACTIVE") 0)
(check "split line" (pt= (cdr (assoc 10 (entget (entlast)))) '(5 5 0)) T)
;; relative & polar coordinates
(command "line" "2,2" "@3,0" "@2<90" "")
(check "polar coord" (pt= (cdr (assoc 11 (entget (entlast)))) '(5 4 0)) T)
;; circle / arc
(command "circle" '(20 20) 5)
(setq c1 (entlast))
(check "circle radius" (cdr (assoc 40 (entget c1))) 5.0)
(command "circle" "2P" '(0 30) '(10 30))
(check "circle 2p" (cdr (assoc 40 (entget (entlast)))) 5.0)
(command "arc" '(10 0) '(0 10) '(-10 0))
(setq a (entget (entlast)))
(check "arc 3p center" (pt= (cdr (assoc 10 a)) '(0 0 0)) T)
(check "arc start ang" (cdr (assoc 50 a)) 0.0)
(check "arc end ang" (cdr (assoc 51 a)) pi)
;; entmod
(setq ed (entget e1))
(setq ed (subst (cons 11 '(20.0 0.0 0.0)) (assoc 11 ed) ed))
(entmod ed)
(check "entmod" (pt= (cdr (assoc 11 (entget e1))) '(20 0 0)) T)
;; layers
(command "-layer" "make" "WALLS" "color" "1" "WALLS" "")
(check "clayer" (getvar "CLAYER") "WALLS")
(check "tblsearch" (cdr (assoc 62 (tblsearch "LAYER" "walls"))) 1)
(command "rectang" '(0 0) '(4 3))
(setq r (entlast))
(check "rect layer" (cdr (assoc 8 (entget r))) "WALLS")
(check "rect verts" (length (vl-remove-if-not '(lambda (p) (= (car p) 10)) (entget r))) 4)
(setvar "CLAYER" "0")
;; selection sets
(setq ss (ssget "X" '((0 . "LINE"))))
(check "ssget X lines" (sslength ss) 5)
(setq ss2 (ssget "X" '((8 . "WALLS"))))
(check "ssget layer" (sslength ss2) 1)
(setq ss3 (ssget "X" '((-4 . "<OR") (0 . "CIRCLE") (0 . "ARC") (-4 . "OR>"))))
(check "ssget OR" (sslength ss3) 3)
(setq ss4 (ssget "X" '((0 . "CIRCLE") (-4 . ">") (40 . 4.0))))
(check "ssget relational" (sslength ss4) 2)
;; MOVE / COPY / ROTATE / SCALE / MIRROR with a selection set
(command "move" c1 "" '(0 0) '(5 0))
(check "move" (pt= (cdr (assoc 10 (entget c1))) '(25 20 0)) T)
(command "copy" c1 "" '(0 0) '(0 10) "")
(check "copy" (pt= (cdr (assoc 10 (entget (entlast)))) '(25 30 0)) T)
(command "line" '(0 0) '(1 0) "")
(setq rl (entlast))
(command "rotate" rl "" '(0 0) 90)
(check "rotate" (pt= (cdr (assoc 11 (entget rl))) '(0 1 0)) T)
(command "scale" rl "" '(0 0) 3)
(check "scale" (pt= (cdr (assoc 11 (entget rl))) '(0 3 0)) T)
(command "mirror" rl "" '(-1 0) '(-1 1) "N")
(check "mirror copy" (pt= (cdr (assoc 11 (entget (entlast)))) '(-2 3 0)) T)
;; OFFSET, TRIM, FILLET
(command "line" '(0 -10) '(10 -10) "")
(setq ol (entlast))
(command "offset" 2 (list ol '(5 -10)) '(5 -5) "")
(check "offset line" (pt= (cdr (assoc 10 (entget (entlast)))) '(0 -8 0)) T)
(command "erase" (entlast) "")
(command "line" '(0 -20) '(10 -20) "")
(setq h (entlast))
(command "line" '(5 -25) '(5 -15) "")
(setq v (entlast))
(command "trim" v "" (list h '(8 -20)) "")
(check "trim" (pt= (cdr (assoc 11 (entget h))) '(5 -20 0)) T)
(command "line" '(20 -20) '(30 -20) "")
(setq f1 (entlast))
(command "line" '(20 -21) '(20 -30) "")
(setq f2 (entlast))
(command "fillet" "R" 0 (list f1 '(25 -20)) (list f2 '(20 -25)))
(check "fillet 0" (pt= (cdr (assoc 10 (entget f2))) '(20 -20 0)) T)
;; polyline with arc segment
(command "pline" '(0 50) '(10 50) "A" '(10 60) "L" '(0 60) "C")
(setq pl (entget (entlast)))
(check "pline closed" (cdr (assoc 70 pl)) 1)
(check "pline bulge" (cdr (assoc 42 pl)) 1.0)
;; text
(command "text" '(0 70) 0.5 0 "Hello Fancy Pencil" "")
(check "text" (cdr (assoc 1 (entget (entlast)))) "Hello Fancy Pencil")
;; block
(command "block" "BOX" '(0 0) r "")
(check "block insert" (cdr (assoc 0 (entget (entlast)))) "INSERT")
(command "insert" "BOX" '(100 100) 2 2 45)
(check "insert scale" (cdr (assoc 41 (entget (entlast)))) 2.0)
;; entmake
(entmake '((0 . "CIRCLE") (10 1.0 2.0 0.0) (40 . 0.75) (8 . "MADE")))
(check "entmake" (cdr (assoc 8 (entget (entlast)))) "MADE")
;; undo
(setq n (sslength (ssget "X")))
(command "line" '(0 0) '(1 1) "")
(command "_.u")
(check "undo" (sslength (ssget "X")) n)
;; explode
(command "explode" (handent (cdr (assoc 5 pl))) "")
(check "explode pline" (cdr (assoc 0 (entget (entlast)))) "LINE")
;; user command
(defun c:sq (/ p) (command "rectang" '(200 200) '(201 201)) (princ))
(c:sq)
(check "c: command" (cdr (assoc 0 (entget (entlast)))) "LWPOLYLINE")
;; DXF round trip
(setq before (sslength (ssget "X")))
(command "saveas" "/tmp/fancypencil-test.dxf")
(command "new")
(check "new empty" (ssget "X") nil)
(command "open" "/tmp/fancypencil-test.dxf")
(check "dxf roundtrip count" (sslength (ssget "X")) before)
(check "dxf layer" (cdr (assoc 62 (tblsearch "LAYER" "WALLS"))) 1)
(check "dxf arc" (sslength (ssget "X" '((0 . "ARC")))) 2)
(princ (strcat "\nCAD tests: " (itoa *pass*) " passed, " (itoa *fail*) " failed.\n"))
;; *error* handler: the error aborts this file, as in AutoCAD, after the handler runs
(defun bad (/ *error*)
  (defun *error* (m) (princ (strcat "*error* handler called with: " m "\n")))
  (command "circle" "nonsense"))
(bad)
(princ "NOT REACHED\n")
