;;; AutoLISP conformance tests for Fancy Pencil. Run: ./fancypencil --tty tests/test-alisp.lsp
(setq *pass* 0 *fail* 0)
(defun check (name got want)
  (if (equal got want 1e-9)
    (setq *pass* (1+ *pass*))
    (progn (setq *fail* (1+ *fail*))
           (princ (strcat "\nFAIL " name ": got " (vl-prin1-to-string got) " want " (vl-prin1-to-string want))))))

;; arithmetic & numbers
(check "int add" (+ 1 2 3) 6)
(check "real add" (+ 1 2.5) 3.5)
(check "int div" (/ 7 2) 3)
(check "real div" (/ 7 2.0) 3.5)
(check "neg" (- 5) -5)
(check "rem" (rem 17 5) 2)
(check "fix" (fix 3.9) 3)
(check "float" (float 3) 3.0)
(check "max mixed" (max 1 2.0 3) 3.0)
(check "expt" (expt 2 10) 1024)
(check "sqrt" (sqrt 16) 4.0)
(check "atan2" (atan 1 1) (/ pi 4))
(check "logand" (logand 7 12) 4)
(check "lsh" (lsh 1 4) 16)
(check "boole xor" (boole 6 5 3) 6)
(check "1+" (1+ 41) 42)
(check "gcd" (gcd 12 18) 6)
;; comparison
(check "=" (= 1 1.0) T)
(check "/=" (/= 1 2) T)
(check "= mixed types" (list (= nil "No") (= "a" "a") (/= "a" nil)) (list nil T T))
(check "= chain" (= 2 2 2.0) T)
(check "< chain" (< 1 2 3) T)
(check "< str" (< "abc" "abd") T)
(check "eq" (eq 'a 'a) T)
(check "equal fuzz" (equal 1.0 1.0000001 0.001) T)
(check "equal lists" (equal '(1 (2 "x")) (list 1 (list 2 "x"))) T)
;; lists
(check "cons dotted" (cons 1 2) '(1 . 2))
(check "cadr" (cadr '(1 2 3)) 2)
(check "caddr" (caddr '(1 2 3)) 3)
(check "cdar" (cdar '((1 . 2))) 2)
(check "nth" (nth 2 '(a b c d)) 'C)
(check "last" (last '(1 2 3)) 3)
(check "append" (append '(1) '(2 3) nil '(4)) '(1 2 3 4))
(check "reverse" (reverse '(1 2 3)) '(3 2 1))
(check "member" (member 2 '(1 2 3)) '(2 3))
(check "assoc" (assoc 8 '((0 . "LINE") (8 . "WALLS"))) '(8 . "WALLS"))
(check "subst" (subst '(8 . "NEW") '(8 . "OLD") '((0 . "LINE") (8 . "OLD"))) '((0 . "LINE") (8 . "NEW")))
(check "mapcar 2" (mapcar '+ '(1 2 3) '(10 20 30)) '(11 22 33))
(check "mapcar lambda" (mapcar '(lambda (x) (* x x)) '(1 2 3)) '(1 4 9))
(check "apply" (apply 'max '(3 9 2)) 9)
(check "vl-sort" (vl-sort '(3 1 2) '<) '(1 2 3))
(check "vl-remove-if" (vl-remove-if 'minusp '(1 -2 3)) '(1 3))
(check "vl-position" (vl-position 'c '(a b c)) 2)
(check "length" (length '(1 2 3)) 3)
(check "listp nil" (listp nil) T)
(check "type" (list (type 1) (type 1.0) (type "a") (type 'a) (type '(1)) (type car)) '(INT REAL STR SYM LIST SUBR))
;; strings
(check "strcat" (strcat "ab" "cd") "abcd")
(check "substr" (substr "Hello World" 7 5) "World")
(check "substr open" (substr "Hello" 2) "ello")
(check "strcase" (strcase "abc") "ABC")
(check "strcase lower" (strcase "ABC" T) "abc")
(check "strlen" (strlen "hello") 5)
(check "itoa" (itoa 42) "42")
(check "atoi" (atoi "17abc") 17)
(check "atof" (atof "2.5") 2.5)
(check "rtos dec" (rtos 3.14159 2 2) "3.14")
(check "rtos arch" (rtos 30.5 4 2) "2'-6 1/2\"")
(check "rtos frac" (rtos 2.75 5 3) "2 3/4")
(check "rtos eng" (rtos 30.5 3 1) "2'-6.5\"")
(check "angtos" (angtos (/ pi 2) 0 0) "90")
(check "angtos dms" (angtos (/ pi 4) 1 4) "45d0'0\"")
(check "distof" (distof "2'6") 30.0)
(check "angtof" (angtof "90") (/ pi 2))
(check "chr/ascii" (list (chr 65) (ascii "A")) '("A" 65))
(check "wcmatch" (list (wcmatch "WALL-1" "WALL*") (wcmatch "A12" "@##") (wcmatch "xyz" "~x*") (wcmatch "DOOR" "WIN*,DOOR")) '(T T nil T))
(check "vl-string-search" (vl-string-search "lo" "hello") 3)
(check "vl-string-subst" (vl-string-subst "J" "H" "Hello") "Jello")
(check "vl-string-trim" (vl-string-trim " " "  x  ") "x")
(check "vl-string->list" (vl-string->list "AB") '(65 66))
(check "read" (read "(1 2 . 3)") '(1 2 . 3))
(check "prin1-to-string" (vl-prin1-to-string "a\"b") "\"a\\\"b\"")
(check "princ real" (vl-princ-to-string 2.0) "2.0")
(check "princ real2" (vl-princ-to-string 3.14159265) "3.14159")
;; control
(defun fact (n) (if (<= n 1) 1 (* n (fact (1- n)))))
(check "recursion" (fact 10) 3628800)
(setq x 0)
(repeat 5 (setq x (+ x 2)))
(check "repeat" x 10)
(setq lst nil)
(foreach i '(1 2 3) (setq lst (cons i lst)))
(check "foreach" lst '(3 2 1))
(setq i 0) (while (< i 4) (setq i (1+ i)))
(check "while" i 4)
(check "cond" (cond ((= 1 2) 'a) ((= 1 1) 'b) (T 'c)) 'B)
(check "and/or" (list (and 1 nil) (or nil 2)) '(nil T))
;; dynamic scoping & locals
(setq g 1)
(defun show-g () g)
(defun bind-g (/ g) (setq g 99) (show-g))
(check "dynamic scope" (bind-g) 99)
(check "local restored" g 1)
(defun add3 (a b c) (+ a b c))
(check "args" (add3 1 2 3) 6)
(check "catch-all" (vl-catch-all-error-p (vl-catch-all-apply '/ '(1 0))) T)
(check "catch msg" (vl-catch-all-error-message (vl-catch-all-apply '/ '(1 0))) "divide by zero")
;; local *error*
(defun test-err (/ *error* result)
  (defun *error* (msg) (setq *errmsg* msg))
  (car 5))
(setq *errmsg* nil)
(vl-catch-all-apply 'test-err nil)
;; geometry
(check "distance" (distance '(0 0) '(3 4)) 5.0)
(check "angle" (angle '(0 0) '(0 1)) (/ pi 2))
(check "polar" (polar '(1 1 0) 0 2) '(3.0 1.0 0.0))
(check "inters" (inters '(0 0) '(2 2) '(0 2) '(2 0)) '(1.0 1.0))
(check "inters nil" (inters '(0 0) '(1 1) '(3 0) '(4 1)) nil)
(check "inters inf" (inters '(0 0) '(1 0) '(5 1) '(5 2) nil) '(5.0 0.0))
;; defun-q list functions
(defun-q sq (x) (* x x))
(check "defun-q" (sq 5) 25)

(princ (strcat "\nAutoLISP tests: " (itoa *pass*) " passed, " (itoa *fail*) " failed.\n"))
(princ)
